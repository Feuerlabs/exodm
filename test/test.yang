module test {

  namespace "http://feuerlabs.com/test";
  prefix test;

  import exosense {
    prefix exo;
  }

  description "Dummy spec for exodm system test";

  list interfaces {
    description "Interface list";
    key "id";

    leaf id {
      description "I/f id - numeric";
      type uint32;
    }

    leaf descr {
      description "I/f description";
      type string;
    }
  }

  rpc echo {
    description "Simple echo RPC";
    input {
      uses exo:std-request;
      leaf message {
	type string;
      }
    }

    output {
      uses exo:std-callback;
      }
    }

  notification echo-callback {
    leaf message {
      type string;
    }
  }

  rpc list-even {
    description "RPC that returns a list of even numbers between 0 and limit";
    input {
      leaf limit { type uint32; }
    }
    output {
      leaf-list evens { type uint32; }
    }
  }

  rpc list-even-direct {
    description "RPC that returns a list of even numbers between 0 and limit";
    input {
      uses exo:std-request;
      leaf protocol {
	type string;
	exo:semantics "protocol";
	default "exodm_bert_direct";
      }
      leaf limit { type uint32; }
    }
    output {
      uses exo:std-callback;
      leaf-list evens { type uint32; }
    }
  }
}
